MY-MIB DEFINITIONS ::= BEGIN

-- A Comment!      


-- IMPORTS: Include definitions from other mibs here, which is always
-- the first item in a MIB file.
IMPORTS
	OBJECT-TYPE, Integer32,
	MODULE-IDENTITY, NOTIFICATION-TYPE, enterprises    FROM SNMPv2-SMI
	MODULE-COMPLIANCE, OBJECT-GROUP                    FROM SNMPv2-CONF;


--
-- A brief description and update information about this mib.
--
firstRooting MODULE-IDENTITY
    LAST-UPDATED "202104281124"            -- 28 April 2021, 11:24
    ORGANIZATION "none"
    CONTACT-INFO "Contact-info."
    DESCRIPTION  "A simple mib for demonstration purposes."
    ::= { enterprises 8073 }


-- wherever you see xRooting, it means it's just rooting in the mib tree, the first rooting 
-- took place on enterprises 8073, which is from SNMPv2-SMI

-- Define typical mib nodes, like where the objects are going to lie.
secondRooting     OBJECT IDENTIFIER ::= { firstRooting 1 }

thirdRooting   OBJECT IDENTIFIER ::= { secondRooting 1 }


myIntMibObject OBJECT-TYPE
    SYNTAX      Integer32
    MAX-ACCESS  read-write
    STATUS      current
    DESCRIPTION
	"This is a nice description. Also this is the mib that represent
                               a simple object.
          But first of all, and last of all, THIS IS A NICE DESCRIPTION"
    DEFVAL { 1 }
    ::= { thirdRooting 4 }


myStringMibObject OBJECT-TYPE
    SYNTAX      OCTET STRING
    MAX-ACCESS  read-write
    STATUS      current
    DESCRIPTION
	"This is a nice description. Also this is the mib that represent 
                    the modem's state - ALIVE/DYING/DEAD.
          So, first of all, and last of all, THIS IS A NICE DESCRIPTION"
    DEFVAL { "ALIVE" }
    ::= { thirdRooting 5 }


--myTrapMibObject NOTIFICATION-TYPE
--	STATUS current
--        OBJECTS { sysLocation }
--	DESCRIPTION "Just a test notification"
--        ::= { thirdRooting 6 }

-- END:  Don't forget this!
END
